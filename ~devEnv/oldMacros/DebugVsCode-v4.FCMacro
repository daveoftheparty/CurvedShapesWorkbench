import os
os.environ["PYDEVD_DISABLE_FILE_VALIDATION"] = "1"
os.environ["PYDEVD_USE_FROZEN_MODULES"] = "0"

import debugpy
import sys
import importlib

try:
	print("are we runnin")

	original_argv = sys.argv
	sys.argv = [sys.argv[0]] # this is required for debug adapter's subprocess to launch FreeCAD cleanly

	debugpy.configure(python="C:/Program Files/FreeCAD 1.1/bin/python.exe")
	debugpy.listen(('localhost', 5678))

	sys.argv = original_argv # restore args now that we've listened.

	print(f"✅ debugpy: Listening on port 5678 (Python: {sys.executable})")

	debugpy.wait_for_client()

	print("✅ debugpy: Debugger attached!")

	# Force reimport so debugpy can instrument the source files
	import CurvedShapes
	import CurvedArray
	importlib.reload(CurvedShapes)
	importlib.reload(CurvedArray)
	print("✅ Reloaded CurvedShapes and CurvedArray for debugging.")
	print("CurvedShapes location:", CurvedShapes.__file__)
	print("CurvedArray location:", CurvedArray.__file__)

except Exception as e:
	import traceback
	print("❌ Failed to start debugpy:", traceback.format_exc())
